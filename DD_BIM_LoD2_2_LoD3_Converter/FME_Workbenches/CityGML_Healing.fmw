FME workspace CityGML_Healing.fmw
Shutdown Python:
      from __future__ import annotations

      import os
      import re
      import shutil
      import sys
      import traceback
      import xml.etree.ElementTree as ET
      from pathlib import Path

      try:
          import fme  # type: ignore
      except ImportError:  # Erlaubt einen lokalen Test außerhalb von FME.
          fme = None  # type: ignore


      # -----------------------------------------------------------------------------
      # Konfiguration
      # -----------------------------------------------------------------------------

      # False ist fachlich sicherer: Der von FME berechnete Envelope enthält alle
      # Koordinaten. Nur auf True setzen, wenn der Envelope zwingend die 2-km-Kachel
      # aus dem Dateinamen darstellen soll.
      FORCE_TILE_ENVELOPE = False

      # Vorhandenes gml:name beibehalten. Bei True wird es auf den Ausgabedateinamen
      # ohne Erweiterung gesetzt.
      UPDATE_EXISTING_TILE_NAME = False

      # Entspricht der Struktur der Eingangsdaten: srsName/srsDimension nur am
      # gml:Envelope, nicht an jeder Einzelgeometrie.
      REMOVE_GEOMETRY_SRS_ATTRIBUTES = True

      # Optional eine Sicherung <datei>.before_shutdown.bak anlegen.
      CREATE_BACKUP = False

      ADV_SRS_NAME = "urn:adv:crs:ETRS89_UTM33*DE_DHHN2016_NH"

      SCHEMA_LOCATION = (
          "http://www.opengis.net/citygml/building/1.0 "
          "http://repository.gdi-de.org/schemas/adv/citygml/building/1.0/buildingLoD2.xsd "
          "http://www.opengis.net/citygml/cityobjectgroup/1.0 "
          "http://repository.gdi-de.org/schemas/adv/citygml/cityobjectgroup/1.0/cityObjectGroupLoD2.xsd "
          "http://www.opengis.net/citygml/appearance/1.0 "
          "http://repository.gdi-de.org/schemas/adv/citygml/appearance/1.0/appearanceLoD2.xsd "
          "http://www.opengis.net/citygml/1.0 "
          "http://repository.gdi-de.org/schemas/adv/citygml/1.0/cityGMLBaseLoD2.xsd "
          "http://www.opengis.net/citygml/generics/1.0 "
          "http://repository.gdi-de.org/schemas/adv/citygml/generics/1.0/genericsLoD2.xsd"
      )

      NS_GML = "http://www.opengis.net/gml"
      NS_XSI = "http://www.w3.org/2001/XMLSchema-instance"
      NS = {"gml": NS_GML, "xsi": NS_XSI}

      TILE_PATTERN = re.compile(r"LoD2_\d+_(\d+)_(\d+)_", re.IGNORECASE)


      # Präfixe für eine stabile Ausgabe registrieren.
      ET.register_namespace("xAL", "urn:oasis:names:tc:ciq:xsdschema:xAL:2.0")
      ET.register_namespace("bldg", "http://www.opengis.net/citygml/building/1.0")
      ET.register_namespace("gml", NS_GML)
      ET.register_namespace("grp", "http://www.opengis.net/citygml/cityobjectgroup/1.0")
      ET.register_namespace("app", "http://www.opengis.net/citygml/appearance/1.0")
      ET.register_namespace("core", "http://www.opengis.net/citygml/1.0")
      ET.register_namespace("gen", "http://www.opengis.net/citygml/generics/1.0")
      ET.register_namespace("xlink", "http://www.w3.org/1999/xlink")
      ET.register_namespace("xsi", NS_XSI)


      def _parse_corner(element: ET.Element, label: str) -> tuple[float, float, float]:
          if not element.text:
              raise ValueError(f"{label} ist leer.")

          values = element.text.split()
          if len(values) != 3:
              raise ValueError(f"{label} muss genau drei Koordinaten enthalten: {element.text!r}")

          return tuple(float(value) for value in values)  # type: ignore[return-value]


      def ensure_tile_name(root: ET.Element, filename: str) -> None:
          desired_name = Path(filename).stem
          name_element = root.find("./gml:name", NS)

          if name_element is None:
              name_element = ET.Element(f"{{{NS_GML}}}name")
              name_element.text = desired_name
              root.insert(0, name_element)
              print(f"gml:name eingefügt: {desired_name}")
          elif UPDATE_EXISTING_TILE_NAME:
              old_name = name_element.text or ""
              name_element.text = desired_name
              print(f"gml:name geändert: {old_name!r} -> {desired_name!r}")
          else:
              print(f"gml:name beibehalten: {name_element.text!r}")


      def configure_envelope(root: ET.Element, filename: str) -> None:
          envelope = root.find(".//gml:Envelope", NS)
          lower_corner = root.find(".//gml:lowerCorner", NS)
          upper_corner = root.find(".//gml:upperCorner", NS)

          if envelope is None or lower_corner is None or upper_corner is None:
              raise ValueError("gml:Envelope mit lowerCorner und upperCorner wurde nicht vollständig gefunden.")

          envelope.set("srsName", ADV_SRS_NAME)
          envelope.set("srsDimension", "3")

          lower_x, lower_y, lower_z = _parse_corner(lower_corner, "gml:lowerCorner")
          upper_x, upper_y, upper_z = _parse_corner(upper_corner, "gml:upperCorner")

          if not FORCE_TILE_ENVELOPE:
              lower_corner.text = f"{lower_x:.3f} {lower_y:.3f} {lower_z:.3f}"
              upper_corner.text = f"{upper_x:.3f} {upper_y:.3f} {upper_z:.3f}"
              print("Envelope-Koordinaten von FME beibehalten.")
              return

          match = TILE_PATTERN.search(filename)
          if match is None:
              raise ValueError(
                  "Kachelkoordinaten konnten nicht aus dem Dateinamen gelesen werden. "
                  "Erwartetes Muster: LoD2_<Zone>_<RW-km>_<HW-km>_..."
              )

          tile_min_x = int(match.group(1)) * 1000
          tile_min_y = int(match.group(2)) * 1000
          tile_max_x = tile_min_x + 2000
          tile_max_y = tile_min_y + 2000

          if (
              lower_x < tile_min_x
              or lower_y < tile_min_y
              or upper_x > tile_max_x
              or upper_y > tile_max_y
          ):
              print(
                  "WARNUNG: Der aktuelle Geometrie-Envelope überschreitet die aus dem "
                  "Dateinamen abgeleitete Kachel. Der erzwungene Kachel-Envelope wird "
                  "nicht alle Geometrien vollständig umschließen."
              )

          lower_corner.text = f"{tile_min_x} {tile_min_y} {lower_z:.3f}"
          upper_corner.text = f"{tile_max_x} {tile_max_y} {upper_z:.3f}"
          print(f"Kachel-Envelope gesetzt: {lower_corner.text} / {upper_corner.text}")


      def remove_geometry_srs_attributes(root: ET.Element) -> int:
          envelope = root.find(".//gml:Envelope", NS)
          if envelope is None:
              raise ValueError("gml:Envelope wurde nicht gefunden.")

          removed = 0
          for element in root.iter():
              if element is envelope:
                  continue
              for attribute_name in ("srsName", "srsDimension"):
                  if attribute_name in element.attrib:
                      del element.attrib[attribute_name]
                      removed += 1

          return removed


      def process_citygml(path: Path) -> None:
          if not path.exists():
              raise FileNotFoundError(f"Ausgabedatei existiert nicht: {path}")
          if path.suffix.lower() not in {".gml", ".xml"}:
              raise ValueError(f"Unerwartete Dateiendung für CityGML: {path.suffix}")

          print(f"Shutdown-Nachbearbeitung: {path}")

          tree = ET.parse(path)
          root = tree.getroot()

          root.set(f"{{{NS_XSI}}}schemaLocation", SCHEMA_LOCATION)
          ensure_tile_name(root, path.name)
          configure_envelope(root, path.name)

          if REMOVE_GEOMETRY_SRS_ATTRIBUTES:
              removed = remove_geometry_srs_attributes(root)
              print(f"Entfernte srsName/srsDimension-Attribute außerhalb des Envelope: {removed}")

          if CREATE_BACKUP:
              backup_path = path.with_suffix(path.suffix + ".before_shutdown.bak")
              shutil.copy2(path, backup_path)
              print(f"Sicherung angelegt: {backup_path}")

          temporary_path = path.with_suffix(path.suffix + ".tmp")
          try:
              tree.write(temporary_path, xml_declaration=True, encoding="UTF-8")
              # Erneut parsen, damit niemals eine syntaktisch defekte XML-Datei ersetzt wird.
              ET.parse(temporary_path)
              os.replace(temporary_path, path)
          finally:
              if temporary_path.exists():
                  temporary_path.unlink()

          print(f"CityGML-Datei erfolgreich nachbearbeitet: {path}")


      def resolve_fme_destination() -> Path:
          if fme is None:
              raise RuntimeError("Das FME-Python-Modul ist nicht verfügbar.")

          for macro_name in ("DestDataset_CITYGML", "DestDataset_CITYGML_1"):
              raw_value = fme.macroValues.get(macro_name)
              if not raw_value:
                  continue

              resolved_value = fme.resolveFMEMacros(str(raw_value)).strip().strip('"')
              absolute_value = fme.getAbsolutePath(resolved_value)
              print(f"Verwendeter FME-Zielparameter: {macro_name}={absolute_value}")
              return Path(absolute_value)

          available = ", ".join(sorted(str(key) for key in fme.macroValues.keys()))
          raise KeyError(
              "Kein CityGML-Zielparameter gefunden. Erwartet wurde "
              "DestDataset_CITYGML oder DestDataset_CITYGML_1. "
              f"Verfügbare Makros: {available}"
          )


      def run_fme_shutdown() -> None:
          if fme is None:
              raise RuntimeError("Das Skript muss in FME ausgeführt werden.")

          # Shutdown-Skripte laufen auch nach fehlgeschlagenen Übersetzungen.
          if not fme.status:
              print(f"Shutdown-Nachbearbeitung übersprungen: {fme.failureMessage}")
              return

          process_citygml(resolve_fme_destination())


      if __name__ == "__main__":
          try:
              if fme is None:
                  if len(sys.argv) != 2:
                      raise SystemExit(f"Aufruf zum Testen: {Path(sys.argv[0]).name} <datei.gml>")
                  process_citygml(Path(sys.argv[1]).resolve())
              else:
                  run_fme_shutdown()
          except Exception as error:
              print(f"FME-Shutdown-Skript fehlgeschlagen: {type(error).__name__}: {error}")
              traceback.print_exc()
              raise

Parameters:
- SourceDataset_CITYGML = C:\Users\Christian\Documents\Master_Geoinformation_Management\Masterarbeit\Heilung-Validierungstools\X_Testdatensatz\00_input\LoD2_33_416_5656_2_SN_BuildingPreferences_14_Buildings_original.gml   # Source CityGML File(s)
- DestDataset_CITYGML = C:\Users\Christian\Documents\Master_Geoinformation_Management\Masterarbeit\Heilung-Validierungstools\XX_Toolvergleich-Test\FME_Test\01_output_fme\Testdaten\LoD2_33_416_5656_2_SN_BuildingPreferences_FME_Healed-test.gml   # Destination CityGML Document

Readers:
- CITYGML_3: CITYGML from $(SourceDataset_CITYGML)

Writers:
- CITYGML_1: CITYGML to $(DestDataset_CITYGML)

GeometryValidator
    ISSUE_ATTR_NAME = _issues
    PRESETS = Custom
    REPAIR = YES
    RULES = CONSECUTIVE_IDENTICAL_VERTICES_2D CHECK_Z]YES]TOLERANCE]0.005]TOLERANCE_CONSECUTIVE_IDENTICAL_VERTICES_2D]0.005 PLANAR_SURFACE CHECK_AREA]DO_NOT_CHECK_AREA]TOLERANCE_MODE]CUSTOM]TOLERANCE_PLANAR_SURFACE]0.00141]ANGULAR_TOLERANCE_MODE]AUTO]ANGULAR_TOLERANCE]<Unused>]TOLERANCE]0.00141 SELF_INTERSECTING CHECK_HOLE_TOUCHING_POLYGON]No]CONNECT_Z_MODE_SI]FIRST_WINS]SELF_INTERSECTION_TOLERANCE]Automatic]VALIDATE_CURVES_POINTS]Yes]INTERSECT_ACROSS_MULTIS]No AREA_ORIENTATION AREA_ORIENTATION]VALID SURFACE_ORIENTATION
    SUMMARY = DETAILED_SUMMARY
    PASSED -> GeometryValidator_6
    REPAIRED -> GeometryValidator_6
GeometryValidator_6
    ISSUE_ATTR_NAME = _issues
    PRESETS = Custom
    REPAIR = YES
    RULES = SHELL_VALIDATION FLIP_APPEARANCE_MODE]FLIP_APPEARANCES SOLID_ORIENTATION  SOLID_VOID_REPAIR
    SUMMARY = DETAILED_SUMMARY
GeometryValidator_5
    ISSUE_ATTR_NAME = _issues
    PRESETS = Custom
    REPAIR = YES
    RULES = CONSECUTIVE_IDENTICAL_VERTICES_2D CHECK_Z]YES]TOLERANCE]0.005]TOLERANCE_CONSECUTIVE_IDENTICAL_VERTICES_2D]0.005 PLANAR_SURFACE CHECK_AREA]DO_NOT_CHECK_AREA]TOLERANCE_MODE]CUSTOM]TOLERANCE_PLANAR_SURFACE]0.00141]ANGULAR_TOLERANCE_MODE]AUTO]ANGULAR_TOLERANCE]<Unused>]TOLERANCE]0.00141 SELF_INTERSECTING CHECK_HOLE_TOUCHING_POLYGON]No]CONNECT_Z_MODE_SI]FIRST_WINS]SELF_INTERSECTION_TOLERANCE]Automatic]VALIDATE_CURVES_POINTS]Yes]INTERSECT_ACROSS_MULTIS]No AREA_ORIENTATION AREA_ORIENTATION]VALID SURFACE_ORIENTATION
    SUMMARY = DETAILED_SUMMARY
    PASSED -> GeometryValidator_7
    FAILED -> GeometryValidator_7
    REPAIRED -> GeometryValidator_7
GeometryValidator_7
    ISSUE_ATTR_NAME = _issues
    PRESETS = Custom
    REPAIR = YES
    RULES = SHELL_VALIDATION FLIP_APPEARANCE_MODE]FLIP_APPEARANCES SOLID_ORIENTATION  SOLID_VOID_REPAIR
    SUMMARY = DETAILED_SUMMARY
Note: Type : RoofSurface
Junction_5
    -> AttributeManager_RoofSurface
AttributeManager_RoofSurface
    ATTR_TABLE:
      REMOVE citygml_function (buffer)
      REMOVE citygml_roof_type (buffer)
      REMOVE citygml_measured_height (real64)
      REMOVE citygml_measured_height_units (buffer)
      REMOVE citygml_storeys_above_ground (uint64)
      REMOVE citygml_storeys_below_ground (uint64)
      REMOVE citygml_outer_building_installation{}.xlink_href (buffer)
      REMOVE citygml_bounded_by{}.xlink_href (buffer)
      REMOVE citygml_consists_of_building_part{}.xlink_href (buffer)
      REMOVE citygml_address{}.xlink_href (buffer)
      REMOVE DatenquelleBodenhoehe (buffer)
      REMOVE DatenquelleDachhoehe (buffer)
      REMOVE DatenquelleGeschossanzahl (buffer)
      REMOVE DatenquelleLage (buffer)
      REMOVE Gemeindeschluessel (buffer)
      REMOVE Geometrietyp2DReferenz (buffer)
      REMOVE Grundrissaktualitaet (buffer)
      REMOVE H_DGM (buffer)
      REMOVE MaxHBuilding (buffer)
      REMOVE MaxZBuilding (buffer)
      REMOVE OBJEKT_ID (buffer)
      REMOVE gml_parent_id_building (buffer)
      REMOVE BldgPartID (buffer)
    -> CityGMLGeometrySetter
Note: Type : WallSurface
Junction_8
    -> AttributeManager_WallSurface
AttributeManager_WallSurface
    ATTR_TABLE:
      REMOVE citygml_function (buffer)
      REMOVE citygml_roof_type (buffer)
      REMOVE citygml_measured_height (real64)
      REMOVE citygml_measured_height_units (buffer)
      REMOVE citygml_storeys_above_ground (uint64)
      REMOVE citygml_storeys_below_ground (uint64)
      REMOVE citygml_outer_building_installation{}.xlink_href (buffer)
      REMOVE citygml_bounded_by{}.xlink_href (buffer)
      REMOVE citygml_consists_of_building_part{}.xlink_href (buffer)
      REMOVE citygml_address{}.xlink_href (buffer)
      REMOVE DatenquelleBodenhoehe (buffer)
      REMOVE DatenquelleDachhoehe (buffer)
      REMOVE DatenquelleGeschossanzahl (buffer)
      REMOVE DatenquelleLage (buffer)
      REMOVE Gemeindeschluessel (buffer)
      REMOVE Geometrietyp2DReferenz (buffer)
      REMOVE Grundrissaktualitaet (buffer)
      REMOVE H_DGM (buffer)
      REMOVE MaxHBuilding (buffer)
      REMOVE MaxZBuilding (buffer)
      REMOVE OBJEKT_ID (buffer)
      REMOVE gml_parent_id_building (buffer)
      REMOVE BldgPartID (buffer)
    -> CityGMLGeometrySetter_2
Note: Type : GroundSurface
Junction_15
    -> AttributeManager_GroundSurface
AttributeManager_GroundSurface
    ATTR_TABLE:
      REMOVE citygml_function (buffer)
      REMOVE citygml_roof_type (buffer)
      REMOVE citygml_measured_height (real64)
      REMOVE citygml_measured_height_units (buffer)
      REMOVE citygml_storeys_above_ground (uint64)
      REMOVE citygml_storeys_below_ground (uint64)
      REMOVE citygml_outer_building_installation{}.xlink_href (buffer)
      REMOVE citygml_bounded_by{}.xlink_href (buffer)
      REMOVE citygml_consists_of_building_part{}.xlink_href (buffer)
      REMOVE citygml_address{}.xlink_href (buffer)
      REMOVE DatenquelleBodenhoehe (buffer)
      REMOVE DatenquelleDachhoehe (buffer)
      REMOVE DatenquelleGeschossanzahl (buffer)
      REMOVE DatenquelleLage (buffer)
      REMOVE Gemeindeschluessel (buffer)
      REMOVE Geometrietyp2DReferenz (buffer)
      REMOVE Grundrissaktualitaet (buffer)
      REMOVE H_DGM (buffer)
      REMOVE MaxHBuilding (buffer)
      REMOVE MaxZBuilding (buffer)
      REMOVE OBJEKT_ID (buffer)
      REMOVE gml_parent_id_building (buffer)
      REMOVE BldgPartID (buffer)
    -> CityGMLGeometrySetter_3

Bookmark: Planarität etc.
BuildingPart (reader CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_function xml_buffer, citygml_roof_type xml_buffer, citygml_measured_height xml_real64, citygml_measured_height_units xml_buffer, citygml_storeys_above_ground xml_uint64, citygml_storeys_below_ground xml_uint64, citygml_level_of_detail{} xml_buffer, citygml_outer_building_installation{}.xlink_href xml_buffer, citygml_bounded_by{}.xlink_href xml_buffer, citygml_consists_of_building_part{}.xlink_href xml_buffer, citygml_address{}.xlink_href xml_buffer, BldgPartID xml_buffer, DatenquelleBodenhoehe xml_buffer, DatenquelleDachhoehe xml_buffer, DatenquelleGeschossanzahl xml_buffer, DatenquelleLage xml_buffer, Grundrissaktualitaet xml_buffer
    -> B_Parts_mit_gml_id [REQUESTOR]
    -> Junction_7
    -> GeometryValidator
Note: Attributes_BParts
Junction_7
    -> Junction_11
Building (reader CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_function xml_buffer, citygml_roof_type xml_buffer, citygml_measured_height xml_real64, citygml_measured_height_units xml_buffer, citygml_storeys_above_ground xml_uint64, citygml_storeys_below_ground xml_uint64, citygml_level_of_detail{} xml_buffer, citygml_outer_building_installation{}.xlink_href xml_buffer, citygml_bounded_by{}.xlink_href xml_buffer, citygml_consists_of_building_part{}.xlink_href xml_buffer, citygml_address{}.xlink_href xml_buffer, DatenquelleBodenhoehe xml_buffer, DatenquelleDachhoehe xml_buffer, DatenquelleGeschossanzahl xml_buffer, DatenquelleLage xml_buffer, Gemeindeschluessel xml_buffer, Geometrietyp2DReferenz xml_buffer, Grundrissaktualitaet xml_buffer,
      H_DGM xml_buffer, MaxHBuilding xml_buffer, MaxZBuilding xml_buffer, OBJEKT_ID xml_buffer
    -> Buildings_mit_gml_id
    -> Junction_12
    -> GeometryValidator_5
Buildings_mit_gml_id: TestFilter
    DEFAULT_VALUE = <UNFILTERED>
    PASSED_TEST_GROUP_OUTPUT = FIRST
    TEST_LIST = "BOOL_OP,OR,COMPOSITE_TEST,""""""1"""""",TEST_CLAUSE,TEST gml_id ATTRIBUTE_HAS_A_VALUE """,gml_id ATTRIBUTE_HAS_A_VALUE
    gml_id ATTRIBUTE_HAS_A_VALUE -> Junction
    gml_id ATTRIBUTE_HAS_A_VALUE -> B_Parts_mit_gml_id [SUPPLIER]
B_Parts_mit_gml_id: FeatureMerger
    ATTR_ACCUM_MODE = Merge Supplier
    ATTR_CONFLICT_RES_LOOKUP = REQUESTOR_IF_CONFLICT
    IGNORE_NULLS = No
    JOIN_KEYS = @Value(gml_parent_id) @Value(gml_id) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeCopier
    USED_SUPPLIER -> Junction_9
AttributeCopier
    ATTR_TABLE = COPY gml_parent_id > gml_parent_id_building
    MISSING_INPUT_ATTRS = REMOVE
    -> Junction
Note: Building & B_Parts mit gml_id
Junction
    -> RoofSurface_mit_gml_id [SUPPLIER]
    -> WallSurface_mit_gml_id [SUPPLIER]
    -> GroundSurface_mit_gml_id [SUPPLIER]
    -> GeometryValidator_2
Note: Attribute_gml_id / _Suplier_BParts
Junction_9
    -> Junction_10
Note: Attributes_Bldg
Junction_12
    -> Junction_13
RoofSurface (reader CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_level_of_detail{} xml_buffer, BldgFaceID xml_buffer, DachName_LOD2 xml_buffer, DachTyp_LOD2 xml_buffer, FACEAREA xml_buffer, NORMAL_AZI xml_buffer, NORMAL_H xml_buffer, STRUKTUR xml_buffer, Z_MAX_ASL xml_buffer, Z_MIN_ASL xml_buffer, Z_Max xml_buffer, Z_Min xml_buffer
    -> RoofSurface_mit_gml_id [REQUESTOR]
RoofSurface_mit_gml_id: FeatureMerger
    ATTR_ACCUM_MODE = Merge Supplier
    ATTR_CONFLICT_RES_LOOKUP = REQUESTOR_IF_CONFLICT
    IGNORE_NULLS = No
    JOIN_KEYS = @Value(gml_parent_id) @Value(gml_id) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> PlanarityFilter
    MERGED -> Junction_2
WallSurface (reader CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_level_of_detail{} xml_buffer, BldgFaceID xml_buffer, DachName_LOD2 xml_buffer, DachTyp_LOD2 xml_buffer, FACEAREA xml_buffer, NORMAL_AZI xml_buffer, NORMAL_H xml_buffer, STRUKTUR xml_buffer, Z_MAX_ASL xml_buffer, Z_MIN_ASL xml_buffer, Z_Max xml_buffer, Z_Min xml_buffer
    -> WallSurface_mit_gml_id [REQUESTOR]
WallSurface_mit_gml_id: FeatureMerger
    ATTR_ACCUM_MODE = Merge Supplier
    ATTR_CONFLICT_RES_LOOKUP = REQUESTOR_IF_CONFLICT
    IGNORE_NULLS = No
    JOIN_KEYS = @Value(gml_parent_id) @Value(gml_id) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> PlanarityFilter_2
    MERGED -> Junction_2
GroundSurface (reader CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_level_of_detail{} xml_buffer, BldgFaceID xml_buffer, FACEAREA xml_buffer, STRUKTUR xml_buffer, Z_MIN_ASL xml_buffer, Z_Min xml_buffer
    -> GroundSurface_mit_gml_id [REQUESTOR]
GroundSurface_mit_gml_id: FeatureMerger
    ATTR_ACCUM_MODE = Merge Supplier
    ATTR_CONFLICT_RES_LOOKUP = REQUESTOR_IF_CONFLICT
    IGNORE_NULLS = No
    JOIN_KEYS = @Value(gml_parent_id) @Value(gml_id) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> PlanarityFilter_3
    MERGED -> Junction_2
Note: all_Surfaces
Junction_2
    -> GeometryValidator_4

Bookmark: XLinks_lod2Solid
Note: BuildingPart
Junction_11
    -> Bldg_or_BPart [RIGHT]
AttributeCreator_xlink
    ATTR_TABLE = SET_TO xlink_href (varchar(200)) = #@Value(_poly_gml_id)
    INPUT_PORT_CONNECTED = CONNECTED
    -> GeometryPropertySetter_xlink
GeometryPropertySetter_xlink
    DO_REMOVE_ATTR = *
    GQUERY:
      for $geom in //geometry
      where $geom/@fme_geometry_type = 'IFMEFace'
      return number($geom/@fme_id)
    OVERWRITE_CHOICE_OPT = yes
    SETTYPE_PARAM = Traits From Attributes
    SRC_ATTRS = xlink_href
    OVERWRITE_CHOICE = Yes
    REMOVE_ATTRIBUTE = Yes
    SET -> Bldg_or_BPart [LEFT]
Bldg_or_BPart: FeatureJoiner
    ATTR_CONFLICT_RES = USE_LEFT
    GEOMETRY_HANDLING = USE_LEFT
    JOIN_KEYS = gml_parent_id gml_id AUTO
    JOIN_MODE = Inner
    JOINED -> BuildingPart
    UNJOINED_LEFT -> Building_without_BParts

Bookmark: Wasserdichte
GeometryValidator_2
    ISSUE_ATTR_NAME = _issues
    PRESETS = Custom
    REPAIR = NO
    RULES = SOLID_VOID_REPAIR FME_CONTROLLER_QUERY_FILE]]FME_CONTROLLER_CHOICE]SOLID_VOID_REPAIR SHELL_VALIDATION FLIP_APPEARANCE_MODE]FLIP_APPEARANCES]FME_CONTROLLER_QUERY_FILE]transformers/dependencies/geometryvalidator9/SHELL_VALIDATION.fme]FME_CONTROLLER_CHOICE]SHELL_VALIDATION SURFACE_ORIENTATION FME_CONTROLLER_QUERY_FILE]]FME_CONTROLLER_CHOICE]SURFACE_ORIENTATION SOLID_ORIENTATION FME_CONTROLLER_QUERY_FILE]]FME_CONTROLLER_CHOICE]SOLID_ORIENTATION AREA_ORIENTATION AREA_ORIENTATION]VALID]FME_CONTROLLER_QUERY_FILE]]FME_CONTROLLER_CHOICE]AREA_ORIENTATION
    SUMMARY = DETAILED_SUMMARY
    ISSUE_LOCATIONS -> TestFilter_2
TestFilter_2
    DEFAULT_VALUE = <UNFILTERED>
    PASSED_TEST_GROUP_OUTPUT = FIRST
    TEST_LIST = "BOOL_OP,OR,COMPOSITE_TEST,""""""1"""""",TEST_CLAUSE,TEST @Value(issue_found) = Invalid Solid Boundaries",Invalid Solid Boundaries,"BOOL_OP,OR,COMPOSITE_TEST,""""""1"""""",TEST_CLAUSE,TEST @Value(issue_found) = Incorrect Solid Orientation",Incorrect Solid Orientation
    Invalid Solid Boundaries -> TestFilter_3
TestFilter_3
    DEFAULT_VALUE = <UNFILTERED>
    PASSED_TEST_GROUP_OUTPUT = FIRST
    TEST_LIST = "BOOL_OP,OR,COMPOSITE_TEST,""""""1"""""",TEST_CLAUSE,TEST @Value(details) = Surface Not Closed",Surface Not Closed,"BOOL_OP,OR,COMPOSITE_TEST,""""""1"""""",TEST_CLAUSE,TEST @Value(details) = Surface Self Intersects",Surface Self Intersects,"BOOL_OP,OR,COMPOSITE_TEST,""""""1"""""",TEST_CLAUSE,TEST @Value(details) = Not Valid 2-Manifold",Not Valid 2-Manifold,"BOOL_OP,OR,COMPOSITE_TEST,""""""1"""""",TEST_CLAUSE,TEST @Value(details) = Face Wrong Orientation",Face Wrong Orientation

Bookmark: Attribute_BuildingPart
Note: B_Parts_mit_gml_id: / Supplier
Junction_10
    -> GeometryRemover
GeometryRemover
    GEOM_NAME_SELECTION = FME_ALL_GEOMETRIES
    REMOVE_COORDSYS = Yes
    -> AttributeManager_5
AttributeManager_5
    ATTR_TABLE = SET_TO gml_parent_id (buffer) = FME_NULL_VALUE
    -> NullAttributeMapper_3
NullAttributeMapper_3
    ATTRCHOICE_ACTION = SELECTED
    ATTRLIST = gml_parent_id
    NULL_TREATMENT_LU = DELETEATTR
    SOURCE_ATTR_VAL_LU = SETNULL
    ATTRCHOICE = Selected Attributes
    NULL_TREATMENT = Missing
    SOURCE_ATTR_VAL = Null
    -> Junction_4
Note: Building
Junction_13
    -> AttributeKeeper
AttributeKeeper
    CREATE_BULK_MODE_FEATURES = NO
    KEEP_ATTRS = citygml_feature_role,gml_name,gml_parent_id,OBJEKT_ID
    -> FeatureJoiner [RIGHT]
AttributeManager
    ATTR_TABLE:
      REMOVE gml_id (buffer)
      REMOVE citygml_feature_role (buffer)
      REMOVE gml_name (buffer)
      REMOVE BldgFaceID (buffer)
      REMOVE DachName_LOD2 (buffer)
      REMOVE DachTyp_LOD2 (buffer)
      REMOVE FACEAREA (buffer)
      REMOVE NORMAL_AZI (buffer)
      REMOVE NORMAL_H (buffer)
      REMOVE STRUKTUR (buffer)
      REMOVE Z_MAX_ASL (buffer)
      REMOVE Z_MIN_ASL (buffer)
      REMOVE Z_Max (buffer)
      REMOVE Z_Min (buffer)
      REMOVE BldgPartID (buffer)
      REMOVE gml_parent_id_building (buffer)
    -> AttributeRemover
AttributeRemover
    -> AttributeRenamer
AttributeRenamer
    ATTR_TABLE = RENAME_SET_DEFAULT gml_parent_id > gml_id
    KEEP_RENAMED_ONLY = no
    MISSING_INPUT_ATTRS = REMOVE
    -> FeatureJoiner [LEFT]
FeatureJoiner
    ATTR_CONFLICT_RES = USE_LEFT
    GEOMETRY_HANDLING = USE_LEFT
    JOIN_KEYS = OBJEKT_ID OBJEKT_ID AUTO
    JOIN_MODE = Inner
    JOINED -> AttributeManager_4
AttributeManager_4
    ATTR_TABLE:
      SET_TO citygml_storeys_above_ground (uint64) = FME_CONDITIONAL:DEFAULT_VALUE'@Value(citygml_storeys_above_ground)'BOOL_OP;OR;COMPOSITE_TEST;1;TEST @Value(citygml_storeys_above_ground) = -1'FME_NULL_VALUE'FME_NUM_CONDITIONS2___
      SET_TO gml_parent_id (buffer) = FME_NULL_VALUE
    -> NullAttributeMapper_2
NullAttributeMapper_2
    ATTRCHOICE_ACTION = SELECTED
    ATTRLIST = gml_parent_id citygml_storeys_above_ground
    NULL_TREATMENT_LU = DELETEATTR
    SOURCE_ATTR_VAL_LU = SETNULL
    ATTRCHOICE = Selected Attributes
    NULL_TREATMENT = Missing
    SOURCE_ATTR_VAL = Null
    -> Junction_4
Junction_4
    -> CityGMLGeometrySetter_5

Bookmark: Planarität
PlanarityFilter
    ANGULAR_TOLERANCE_CHOICE_LOOKUP = AUTO
    OUTPUT_LOOKUP = EXPOSE_SURFACE_NORMAL
    THICKNESS_TOLERANCE = 0.00141
    THICKNESS_TOLERANCE_CHOICE_LOOKUP = CUSTOM
    ANGULAR_TOLERANCE_CHOICE = Automatic
    OUTPUT_NORMAL = Yes
    THICKNESS_TOLERANCE_CHOICE = Custom
    NOT_PLANAR -> Gruppieren_nach_gml_id
PlanarityFilter_2
    ANGULAR_TOLERANCE_CHOICE_LOOKUP = AUTO
    OUTPUT_LOOKUP = EXPOSE_SURFACE_NORMAL
    THICKNESS_TOLERANCE = 0.00141
    THICKNESS_TOLERANCE_CHOICE_LOOKUP = CUSTOM
    ANGULAR_TOLERANCE_CHOICE = Automatic
    OUTPUT_NORMAL = Yes
    THICKNESS_TOLERANCE_CHOICE = Custom
    NOT_PLANAR -> Gruppieren_nach_gml_id
PlanarityFilter_3
    ANGULAR_TOLERANCE_CHOICE_LOOKUP = AUTO
    OUTPUT_LOOKUP = EXPOSE_SURFACE_NORMAL
    THICKNESS_TOLERANCE = 0.00141
    THICKNESS_TOLERANCE_CHOICE_LOOKUP = CUSTOM
    ANGULAR_TOLERANCE_CHOICE = Automatic
    OUTPUT_NORMAL = Yes
    THICKNESS_TOLERANCE_CHOICE = Custom
    NOT_PLANAR -> Gruppieren_nach_gml_id

Bookmark: CityGML_Healing_&_REBUILD
GeometryValidator_4
    ISSUE_ATTR_NAME = _issues
    PRESETS = Custom
    REPAIR = YES
    RULES = CONSECUTIVE_IDENTICAL_VERTICES_2D CHECK_Z]YES]TOLERANCE]0.005]TOLERANCE_CONSECUTIVE_IDENTICAL_VERTICES_2D]0.005 TYPE_REPAIR CONNECT_Z_MODE]AVERAGE]ARC_ENDPOINT_TOLERANCE_MODE]Custom]ARC_ENDPOINT_TOLERANCE]0.00173 SELF_INTERSECTING CHECK_HOLE_TOUCHING_POLYGON]No]CONNECT_Z_MODE_SI]FIRST_WINS]SELF_INTERSECTION_TOLERANCE]0.0001]VALIDATE_CURVES_POINTS]Yes]INTERSECT_ACROSS_MULTIS]No PLANAR_SURFACE CHECK_AREA]DO_NOT_CHECK_AREA]TOLERANCE_MODE]CUSTOM]TOLERANCE_PLANAR_SURFACE]0.00141]ANGULAR_TOLERANCE_MODE]AUTO]ANGULAR_TOLERANCE]<Unused>]TOLERANCE]0.00141 SURFACE_ORIENTATION  AREA_ORIENTATION AREA_ORIENTATION]VALID SHELL_VALIDATION FLIP_APPEARANCE_MODE]FLIP_APPEARANCES SOLID_VOID_REPAIR  SOLID_ORIENTATION
    SUMMARY = DETAILED_SUMMARY
    PASSED -> GeometryFilter
    REPAIRED -> GeometryFilter
GeometryFilter
    FILTER_MODE = SIMPLE
    FILTER_MULTI = FILTER_TYPES]Area Surface Solid]FILTER_TYPES_Simple]Area Surface Solid
    FILTER_TYPES = Area Surface Solid
    FILTER_TYPES_Simple = Area Surface Solid
    Surface -> GeometryValidator_3
    Surface -> Junction_16
    <UNFILTERED> -> GeometryFilter_4
Junction_16
    -> Deaggregator

Bookmark: Kontrolle_nach_Repair
GeometryValidator_3
    ISSUE_ATTR_NAME = _issues
    PRESETS = Custom
    REPAIR = NO
    RULES = CONSECUTIVE_IDENTICAL_VERTICES_2D CHECK_Z]YES]TOLERANCE]0.00173]FME_CONTROLLER_QUERY_FILE]]FME_CONTROLLER_CHOICE]CONSECUTIVE_IDENTICAL_VERTICES_2D SELF_INTERSECTING CHECK_HOLE_TOUCHING_POLYGON]No]CONNECT_Z_MODE_SI]FIRST_WINS]SELF_INTERSECTION_TOLERANCE]Automatic]VALIDATE_CURVES_POINTS]Yes]INTERSECT_ACROSS_MULTIS]No]FME_CONTROLLER_QUERY_FILE]]FME_CONTROLLER_CHOICE]SELF_INTERSECTING SHELL_VALIDATION FLIP_APPEARANCE_MODE]FLIP_APPEARANCES]FME_CONTROLLER_QUERY_FILE]]FME_CONTROLLER_CHOICE]SHELL_VALIDATION PLANAR_SURFACE CHECK_AREA]DO_NOT_CHECK_AREA]TOLERANCE_MODE]CUSTOM]TOLERANCE]0.00141]ANGULAR_TOLERANCE_MODE]AUTO]ANGULAR_TOLERANCE]<Unused>]FME_CONTROLLER_QUERY_FILE]]FME_CONTROLLER_CHOICE]PLANAR_SURFACE TYPE_REPAIR CONNECT_Z_MODE]FIRST_WINS]ARC_ENDPOINT_TOLERANCE_MODE]Auto]ARC_ENDPOINT_TOLERANCE]<Unused>]FME_CONTROLLER_QUERY_FILE]]FME_CONTROLLER_CHOICE]TYPE_REPAIR
    SUMMARY = DETAILED_SUMMARY
    ISSUE_LOCATIONS -> TestFilter
TestFilter
    DEFAULT_VALUE = <UNFILTERED>
    PASSED_TEST_GROUP_OUTPUT = FIRST
    TEST_LIST = "BOOL_OP,OR,COMPOSITE_TEST,""""""1"""""",TEST_CLAUSE,TEST @Value(issue_found) = Self-Intersections in 2D",Self-Intersections in 2D,"BOOL_OP,OR,COMPOSITE_TEST,""""""1"""""",TEST_CLAUSE,TEST @Value(issue_found) = Invalid Solid Boundaries",Invalid Solid Boundaries,"BOOL_OP,OR,COMPOSITE_TEST,""""""1"""""",TEST_CLAUSE,TEST @Value(issue_found) = Duplicate Consecutive Points in 3D",Duplicate Consecutive Points,"BOOL_OP,OR,COMPOSITE_TEST,""""""1"""""",TEST_CLAUSE,TEST @Value(issue_found) = Non-Planar Surfaces",Non-Planar Surfaces
    Non-Planar Surfaces -> Gruppieren_nach_gml_id_2
Gruppieren_nach_gml_id_2: Aggregator
    ACCUM_ATTRS = None
    AGGREGATE_TYPE = Homogeneous Collection (If Possible)
    GROUP_BY = gml_parent_id
    MODE = Geometry - Assemble One Level
    SEP = ,
    AGGREGATE -> non_planar_Buildings_2
non_planar_Buildings_2: Tester
    BOOL_OP = OR
    TEST_CLAUSE = CASE_INSENSITIVE_TEST @Value(gml_parent_id) BEGINS_WITH Part
    TEST_MODE = CASE_INSENSITIVE_TEST

Bookmark: Spezielle_Reparutur(Extra)_MultiCurve
GeometryFilter_4
    FILTER_MODE = COMPLETE
    FILTER_MULTI = FILTER_TYPES]MultiCurve]FILTER_TYPES_Complete]MultiCurve]INSTANCES]CAST
    FILTER_TYPES = MultiCurve
    FILTER_TYPES_Complete = MultiCurve
    INSTANCES = CAST
    MultiCurve -> Deaggregator_MultiCurve
Deaggregator_MultiCurve
    EXPLODE_INSTANCES = No
    GEOM_LABEL_FIELD = _geometry_label
    LIST_ATTR_MODE_LOOKUP = LEAN
    RECURSIVE = Yes
    SPLIT_COMPOSITES = Yes
    DEAGGREGATED -> LineCloser
LineCloser
    CONNECT_Z_MODE_LOOKUP = FIRST_WINS
    CONNECT_Z_MODE = First Wins
    AREA -> DonutBuilder
DonutBuilder
    ATTR_ACCUM_MODE = Merge Hole
    ATTR_CONFLICT_RES_LOOKUP = ORIGINAL_IF_CONFLICT
    CONNECT_Z_MODE_LOOKUP = FIRST_WINS
    GROUP_BY = BldgFaceID gml_parent_id
    TAG_HOLES = NO
    ATTR_CONFLICT_RES = Use Outer Shell
    CONNECT_Z_MODE = First Wins
    DROP = yes
    AREA -> FaceReplacer
FaceReplacer
    ANGULAR_TOLERANCE_CHOICE_LOOKUP = AUTO
    THICKNESS_TOLERANCE_CHOICE_LOOKUP = AUTO
    ANGULAR_TOLERANCE_CHOICE = Automatic
    THICKNESS_TOLERANCE_CHOICE = Automatic
    -> Junction_16

Bookmark: Polygon_IDs
Deaggregator
    EXPLODE_INSTANCES = No
    GEOM_LABEL_FIELD = _geometry_label
    LIST_ATTR_MODE_LOOKUP = LEAN
    RECURSIVE = Yes
    SPLIT_COMPOSITES = Yes
    DEAGGREGATED -> Sorter
Sorter
    SORT_PARM = OBJEKT_ID NATURAL ASCENDING NON_VALUES_AFTER_VALUES BldgPartID NATURAL ASCENDING NON_VALUES_AFTER_VALUES BldgFaceID NATURAL ASCENDING NON_VALUES_AFTER_VALUES
    SORTED -> Counter
Counter
    CNT_ATTR = _count
    GROUP_BY = gml_parent_id BldgFaceID
    SCOPE = Local
    START = 0
    -> AttributeCreator
AttributeCreator
    ATTR_TABLE:
      SET_TO _poly_gml_id (varchar(200)) = Poly_@Value(BldgFaceID)_@Value(_count)
      SET_TO gml_id (buffer) = Poly_@Value(BldgFaceID)_@Value(_count)
    INPUT_PORT_CONNECTED = CONNECTED
    -> GeometryPropertySetter_Polygon_ID
GeometryPropertySetter_Polygon_ID
    DO_REMOVE_ATTR = NOT_THIS_TIME
    GQUERY:
      for $geom in //geometry
      where $geom/@fme_geometry_type = 'IFMEFace'
      return number($geom/@fme_id)
    OVERWRITE_CHOICE_OPT = yes
    SETTYPE_PARAM = Traits From Attributes
    SRC_ATTRS = gml_id
    OVERWRITE_CHOICE = Yes
    REMOVE_ATTRIBUTE = No
    SET -> AttributeCreator_Surface_ID
AttributeCreator_Surface_ID
    ATTR_TABLE = SET_TO gml_id (buffer) = Face_@Value(BldgFaceID)_@Value(_count)
    INPUT_PORT_CONNECTED = CONNECTED
    -> Aggregator_BSurfaces
    -> AttributeCreator_xlink

Bookmark: BoundarySurfaces
Aggregator_BSurfaces
    ACCUM_ATTRS = One
    AGGREGATE_TYPE = OUTPUT_MULTI
    GROUP_BY = BldgFaceID gml_parent_id _count
    MODE = Geometry - Assemble One Level
    SEP = ,
    AGGREGATE -> Type
Type: TestFilter
    DEFAULT_VALUE = <UNFILTERED>
    PASSED_TEST_GROUP_OUTPUT = FIRST
    TEST_LIST = "BOOL_OP,OR,COMPOSITE_TEST,""""""1"""""",TEST_CLAUSE,TEST @Value(STRUKTUR) = Dach",RoofSurface,"BOOL_OP,OR,COMPOSITE_TEST,""""""1"""""",TEST_CLAUSE,TEST @Value(STRUKTUR) = Wand",WallSurface,"BOOL_OP,OR,COMPOSITE_TEST,""""""1"""""",TEST_CLAUSE,TEST @Value(STRUKTUR) = Boden",GroundSurface
    RoofSurface -> Junction_3
    WallSurface -> Junction_6
    GroundSurface -> Junction_14
Note: RoofSurface : Input
Junction_3
    -> Junction_5
Note: WallSurface : Input
Junction_6
    -> Junction_8
Note: GroundSurface: Input
Junction_14
    -> Junction_15

Bookmark: CityGML-Export
CityGMLGeometrySetter
    GEOM = lod2MultiSurface
    ROLE = boundedBy
    -> RoofSurface (writer CITYGML_1)
RoofSurface (writer CITYGML_1)
    attributes: citygml_feature_role xml_buffer, citygml_target_uri xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_level_of_detail{} xml_buffer, BldgFaceID xml_buffer, DachName_LOD2 xml_buffer, DachTyp_LOD2 xml_buffer, FACEAREA xml_buffer, NORMAL_AZI xml_buffer, NORMAL_H xml_buffer, STRUKTUR xml_buffer, Z_MAX_ASL xml_buffer, Z_MIN_ASL xml_buffer, Z_Max xml_buffer, Z_Min xml_buffer, _issues{}.count xml_uint32, _issues{}.issue_found xml_buffer, _issues{}.location_sample.x xml_real64, _issues{}.location_sample.y xml_real64, _issues{}.location_sample.z xml_real64, _count xml_int64,
      _poly_gml_id xml_char(200), _geometry_label xml_buffer
CityGMLGeometrySetter_2
    GEOM = lod2MultiSurface
    ROLE = boundedBy
    -> WallSurface (writer CITYGML_1)
WallSurface (writer CITYGML_1)
    attributes: citygml_feature_role xml_buffer, citygml_target_uri xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_level_of_detail{} xml_buffer, BldgFaceID xml_buffer, DachName_LOD2 xml_buffer, DachTyp_LOD2 xml_buffer, FACEAREA xml_buffer, NORMAL_AZI xml_buffer, NORMAL_H xml_buffer, STRUKTUR xml_buffer, Z_MAX_ASL xml_buffer, Z_MIN_ASL xml_buffer, Z_Max xml_buffer, Z_Min xml_buffer, _issues{}.count xml_uint32, _issues{}.issue_found xml_buffer, _issues{}.location_sample.x xml_real64, _issues{}.location_sample.y xml_real64, _issues{}.location_sample.z xml_real64, _count xml_int64,
      _poly_gml_id xml_char(200), _geometry_label xml_buffer
CityGMLGeometrySetter_3
    GEOM = lod2MultiSurface
    ROLE = boundedBy
    -> GroundSurface (writer CITYGML_1)
GroundSurface (writer CITYGML_1)
    attributes: citygml_feature_role xml_buffer, citygml_target_uri xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_level_of_detail{} xml_buffer, BldgFaceID xml_buffer, DachName_LOD2 xml_buffer, DachTyp_LOD2 xml_buffer, FACEAREA xml_buffer, NORMAL_AZI xml_buffer, NORMAL_H xml_buffer, STRUKTUR xml_buffer, Z_MAX_ASL xml_buffer, Z_MIN_ASL xml_buffer, Z_Max xml_buffer, Z_Min xml_buffer, _issues{}.count xml_uint32, _issues{}.issue_found xml_buffer, _issues{}.location_sample.x xml_real64, _issues{}.location_sample.y xml_real64, _issues{}.location_sample.z xml_real64, _count xml_int64,
      _poly_gml_id xml_char(200), _geometry_label xml_buffer
CityGMLGeometrySetter_4
    GEOM = lod2Solid
    ROLE = consistsOfBuildingPart
    -> BuildingPart (writer CITYGML_1)
BuildingPart (writer CITYGML_1)
    attributes: citygml_feature_role xml_buffer, citygml_target_uri xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_function xml_buffer, citygml_roof_type xml_buffer, citygml_measured_height xml_real64, citygml_measured_height_units xml_buffer, citygml_storeys_above_ground xml_uint64, citygml_storeys_below_ground xml_uint64, citygml_level_of_detail{} xml_buffer, citygml_outer_building_installation{}.xlink_href xml_buffer, citygml_bounded_by{}.xlink_href xml_buffer, citygml_consists_of_building_part{}.xlink_href xml_buffer, citygml_address{}.xlink_href xml_buffer, BldgPartID xml_buffer, DatenquelleBodenhoehe xml_buffer, DatenquelleDachhoehe xml_buffer, DatenquelleGeschossanzahl xml_buffer, DatenquelleLage xml_buffer, Grundrissaktualitaet xml_buffer, _issues{}.count xml_uint32,
      _issues{}.issue_found xml_buffer, _issues{}.location_sample.x xml_real64, _issues{}.location_sample.y xml_real64, _issues{}.location_sample.z xml_real64, xlink_href xml_char(200), _poly_gml_id xml_char(200), _geometry_label xml_buffer, _count xml_int64, _surface_count xml_uint32
CityGMLGeometrySetter_5
    GEOM = lod2Solid
    ROLE = cityObjectMember
    -> Building (writer CITYGML_1)
Building (writer CITYGML_1)
    attributes: citygml_feature_role xml_buffer, citygml_target_uri xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_level_of_detail{} xml_buffer, citygml_function xml_buffer, citygml_roof_type xml_buffer, citygml_measured_height xml_real64, citygml_measured_height_units xml_buffer, citygml_storeys_above_ground xml_uint64, citygml_storeys_below_ground xml_uint64, citygml_outer_building_installation{}.xlink_href xml_buffer, citygml_bounded_by{}.xlink_href xml_buffer, citygml_consists_of_building_part{}.xlink_href xml_buffer, citygml_address{}.xlink_href xml_buffer, DatenquelleBodenhoehe xml_buffer, DatenquelleDachhoehe xml_buffer, DatenquelleGeschossanzahl xml_buffer, DatenquelleLage xml_buffer, Grundrissaktualitaet xml_buffer, Gemeindeschluessel xml_buffer, Geometrietyp2DReferenz xml_buffer,
      H_DGM xml_buffer, MaxHBuilding xml_buffer, MaxZBuilding xml_buffer, OBJEKT_ID xml_buffer, _issues{}.count xml_uint32, _issues{}.issue_found xml_buffer, _issues{}.location_sample.x xml_real64, _issues{}.location_sample.y xml_real64, _issues{}.location_sample.z xml_real64, xlink_href xml_char(200), _poly_gml_id xml_char(200), _geometry_label xml_buffer, _count xml_int64, numReferences xml_uint32
Address (reader CITYGML_3)
    attributes: citygml_target_uri xml_buffer, citygml_feature_role xml_buffer, citygml_feature_role_attr_name xml_buffer, citygml_feature_role_attr_val xml_buffer, gml_description xml_buffer, gml_name xml_buffer, citygml_address xml_xml
    -> Address (writer CITYGML_1)
Address (writer CITYGML_1)
    attributes: citygml_target_uri xml_buffer, citygml_feature_role xml_buffer, citygml_feature_role_attr_name xml_buffer, citygml_feature_role_attr_val xml_buffer, gml_description xml_buffer, gml_name xml_buffer, citygml_address xml_xml
CityModel (reader CITYGML_3)
    attributes: citygml_target_uri xml_buffer, gml_description xml_buffer, gml_name xml_buffer, citygml_city_object_member{}.xlink_href xml_buffer, citygml_appearance_member{}.xlink_href xml_buffer, gml_feature_member{}.xlink_href xml_buffer
    -> CityModel (writer CITYGML_1)
CityModel (writer CITYGML_1)
    attributes: citygml_target_uri xml_buffer, gml_description xml_buffer, gml_name xml_buffer, citygml_city_object_member{}.xlink_href xml_buffer, citygml_appearance_member{}.xlink_href xml_buffer, gml_feature_member{}.xlink_href xml_buffer

Bookmark: Solid_Building
BuildingPart: Aggregator
    ACCUM_ATTRS = One
    AGGREGATE_TYPE = Homogeneous Collection (If Possible)
    COUNT_ATTR = _surface_count
    GROUP_BY = gml_parent_id
    MODE = Geometry - Assemble One Level
    SEP = ,
    AGGREGATE -> GeometryFilter_3
GeometryFilter_3
    FILTER_MODE = SIMPLE
    FILTER_MULTI = FILTER_TYPES]Surface]FILTER_TYPES_Simple]Surface
    FILTER_TYPES = Surface
    FILTER_TYPES_Simple = Surface
    Surface -> GeometryCoercer_2
GeometryCoercer_2
    GQUERY:
      for $geom in //geometry
      where $geom/count(parent::geometry) = 0
      return number($geom/@fme_id)
    KIND = fme_brep_solid
    COERCED -> GeometryPropertyRemover
GeometryPropertyRemover
    REGEX_FILTER = ^gml_id$
    REMOVETYPE_PARAM = REMOVE_TRAITS
    REMOVE_ALL = No
    REMOVED -> AttributeManager_3

Bookmark: Attribute_Building
AttributeManager_3
    ATTR_TABLE:
      REMOVE gml_id (buffer)
      SET_TO gml_name (buffer) = FME_NULL_VALUE
    -> NullAttributeMapper
NullAttributeMapper
    ATTRCHOICE_ACTION = SELECTED
    ATTRLIST = gml_name
    NULL_TREATMENT_LU = DELETEATTR
    SOURCE_ATTR_VAL_LU = SETNULL
    ATTRCHOICE = Selected Attributes
    NULL_TREATMENT = Missing
    SOURCE_ATTR_VAL = Null
    -> AttributeRenamer_3
AttributeRenamer_3
    ATTR_TABLE:
      RENAME_SET_DEFAULT gml_parent_id > gml_id
      RENAME_SET_DEFAULT gml_parent_id_building > gml_parent_id
    KEEP_RENAMED_ONLY = no
    MISSING_INPUT_ATTRS = REMOVE
    -> AttributeManager_BPart
AttributeManager_BPart
    ATTR_TABLE:
      REMOVE BldgFaceID (buffer)
      REMOVE DachName_LOD2 (buffer)
      REMOVE DachTyp_LOD2 (buffer)
      REMOVE FACEAREA (buffer)
      REMOVE NORMAL_AZI (buffer)
      REMOVE NORMAL_H (buffer)
      REMOVE STRUKTUR (buffer)
      REMOVE Z_MAX_ASL (buffer)
      REMOVE Z_MIN_ASL (buffer)
      REMOVE Z_Max (buffer)
      REMOVE Z_Min (buffer)
      REMOVE Gemeindeschluessel (buffer)
      REMOVE Geometrietyp2DReferenz (buffer)
      REMOVE H_DGM (buffer)
      REMOVE MaxHBuilding (buffer)
      REMOVE MaxZBuilding (buffer)
      REMOVE OBJEKT_ID (buffer)
    -> Tester_2
Tester_2
    BOOL_OP = AND
    TEST_CLAUSE:
      TEST gml_id ATTRIBUTE_HAS_A_VALUE ""
      CASE_INSENSITIVE_TEST @Value(gml_id) BEGINS_WITH Part_
      TEST gml_parent_id ATTRIBUTE_HAS_A_VALUE ""
      CASE_INSENSITIVE_TEST @Value(gml_parent_id) BEGINS_WITH DESNALK
      TEST @Value(gml_id) != @Value(gml_parent_id)
    TEST_MODE = TEST
    PASSED -> CityGMLGeometrySetter_4

Bookmark: Solid_BuildingPart
Building_without_BParts: Aggregator
    ACCUM_ATTRS = One
    AGGREGATE_TYPE = Homogeneous Collection (If Possible)
    GROUP_BY = gml_parent_id
    MODE = Geometry - Assemble One Level
    SEP = ,
    AGGREGATE -> GeometryFilter_2
GeometryFilter_2
    FILTER_MODE = SIMPLE
    FILTER_MULTI = FILTER_TYPES]Surface]FILTER_TYPES_Simple]Surface
    FILTER_TYPES = Surface
    FILTER_TYPES_Simple = Surface
    Surface -> GeometryCoercer
GeometryCoercer
    GQUERY:
      for $geom in //geometry
      where $geom/count(parent::geometry) = 0
      return number($geom/@fme_id)
    KIND = fme_brep_solid
    COERCED -> GeometryPropertyRemover_2
GeometryPropertyRemover_2
    REGEX_FILTER = ^gml_id$
    REMOVETYPE_PARAM = REMOVE_TRAITS
    REMOVE_ALL = No
    REMOVED -> AttributeManager

Bookmark: fehlerhafte Gebäude (Planarität)
Gruppieren_nach_gml_id: Aggregator
    ACCUM_ATTRS = None
    AGGREGATE_TYPE = Homogeneous Collection (If Possible)
    GROUP_BY = gml_parent_id
    MODE = Geometry - Assemble One Level
    SEP = ,
    AGGREGATE -> non_planar_Buildings
non_planar_Buildings: Tester
    BOOL_OP = OR
    TEST_CLAUSE = CASE_INSENSITIVE_TEST @Value(gml_parent_id) BEGINS_WITH Part
    TEST_MODE = CASE_INSENSITIVE_TEST
