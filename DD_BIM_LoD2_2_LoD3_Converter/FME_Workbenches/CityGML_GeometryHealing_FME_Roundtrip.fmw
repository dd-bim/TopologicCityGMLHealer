FME workspace CityGML_GeometryHealing_FME_Roundtrip.fmw

Parameters:
- SourceDataset_CITYGML = $(FME_MF_DIR)gml2sql2gml\sqltest\output\LoD2_33_416_5656_2_SN_BuildingPreferences_14_Buildings.gml   # Source CityGML File(s)
- DestDataset_CITYGML = $(FME_MF_DIR)gml2sql2gml\sqltest\output\LoD2_33_416_5656_2_SN_BuildingPreferences_14_Buildings_FME_Healing_Attempt2   # Destination CityGML Document

Readers:
- CITYGML_1: CITYGML from $(SourceDataset_CITYGML)

Writers:
- CITYGML_2: CITYGML to $(DestDataset_CITYGML)

GeometryValidator_4
    ISSUE_ATTR_NAME = _issues
    PRESETS = Custom
    REPAIR = YES
    RULES = CONSECUTIVE_IDENTICAL_VERTICES_2D CHECK_Z]YES]TOLERANCE]0.00173]FME_CONTROLLER_QUERY_FILE]]FME_CONTROLLER_CHOICE]CONSECUTIVE_IDENTICAL_VERTICES_2D SELF_INTERSECTING CHECK_HOLE_TOUCHING_POLYGON]No]CONNECT_Z_MODE_SI]FIRST_WINS]SELF_INTERSECTION_TOLERANCE]Automatic]VALIDATE_CURVES_POINTS]Yes]INTERSECT_ACROSS_MULTIS]No]FME_CONTROLLER_QUERY_FILE]]FME_CONTROLLER_CHOICE]SELF_INTERSECTING SHELL_VALIDATION FLIP_APPEARANCE_MODE]FLIP_APPEARANCES]FME_CONTROLLER_QUERY_FILE]]FME_CONTROLLER_CHOICE]SHELL_VALIDATION PLANAR_SURFACE CHECK_AREA]DO_NOT_CHECK_AREA]TOLERANCE_MODE]CUSTOM]TOLERANCE]0.00141]ANGULAR_TOLERANCE_MODE]AUTO]ANGULAR_TOLERANCE]<Unused>]FME_CONTROLLER_QUERY_FILE]]FME_CONTROLLER_CHOICE]PLANAR_SURFACE SOLID_VOID_REPAIR FME_CONTROLLER_QUERY_FILE]]FME_CONTROLLER_CHOICE]SOLID_VOID_REPAIR SURFACE_ORIENTATION FME_CONTROLLER_QUERY_FILE]]FME_CONTROLLER_CHOICE]SURFACE_ORIENTATION SOLID_ORIENTATION FME_CONTROLLER_QUERY_FILE]]FME_CONTROLLER_CHOICE]SOLID_ORIENTATION AREA_ORIENTATION AREA_ORIENTATION]VALID]FME_CONTROLLER_QUERY_FILE]]FME_CONTROLLER_CHOICE]AREA_ORIENTATION TYPE_REPAIR CONNECT_Z_MODE]FIRST_WINS]ARC_ENDPOINT_TOLERANCE_MODE]Custom]ARC_ENDPOINT_TOLERANCE]0.00141]FME_CONTROLLER_QUERY_FILE]]FME_CONTROLLER_CHOICE]TYPE_REPAIR
    SUMMARY = DETAILED_SUMMARY
    PASSED -> WallSurface (writer CITYGML_2)
    REPAIRED -> WallSurface (writer CITYGML_2)
GeometryValidator_2
    ISSUE_ATTR_NAME = _issues
    PRESETS = Custom
    REPAIR = YES
    RULES = CONSECUTIVE_IDENTICAL_VERTICES_2D CHECK_Z]YES]TOLERANCE]0.00173]FME_CONTROLLER_QUERY_FILE]]FME_CONTROLLER_CHOICE]CONSECUTIVE_IDENTICAL_VERTICES_2D SELF_INTERSECTING CHECK_HOLE_TOUCHING_POLYGON]No]CONNECT_Z_MODE_SI]FIRST_WINS]SELF_INTERSECTION_TOLERANCE]Automatic]VALIDATE_CURVES_POINTS]Yes]INTERSECT_ACROSS_MULTIS]No]FME_CONTROLLER_QUERY_FILE]]FME_CONTROLLER_CHOICE]SELF_INTERSECTING SHELL_VALIDATION FLIP_APPEARANCE_MODE]FLIP_APPEARANCES]FME_CONTROLLER_QUERY_FILE]]FME_CONTROLLER_CHOICE]SHELL_VALIDATION PLANAR_SURFACE CHECK_AREA]DO_NOT_CHECK_AREA]TOLERANCE_MODE]CUSTOM]TOLERANCE]0.00141]ANGULAR_TOLERANCE_MODE]AUTO]ANGULAR_TOLERANCE]<Unused>]FME_CONTROLLER_QUERY_FILE]]FME_CONTROLLER_CHOICE]PLANAR_SURFACE SOLID_VOID_REPAIR FME_CONTROLLER_QUERY_FILE]]FME_CONTROLLER_CHOICE]SOLID_VOID_REPAIR SURFACE_ORIENTATION FME_CONTROLLER_QUERY_FILE]]FME_CONTROLLER_CHOICE]SURFACE_ORIENTATION SOLID_ORIENTATION FME_CONTROLLER_QUERY_FILE]]FME_CONTROLLER_CHOICE]SOLID_ORIENTATION AREA_ORIENTATION AREA_ORIENTATION]VALID]FME_CONTROLLER_QUERY_FILE]]FME_CONTROLLER_CHOICE]AREA_ORIENTATION TYPE_REPAIR CONNECT_Z_MODE]FIRST_WINS]ARC_ENDPOINT_TOLERANCE_MODE]Custom]ARC_ENDPOINT_TOLERANCE]0.00141]FME_CONTROLLER_QUERY_FILE]]FME_CONTROLLER_CHOICE]TYPE_REPAIR
    SUMMARY = DETAILED_SUMMARY
    PASSED -> RoofSurface (writer CITYGML_2)
    REPAIRED -> RoofSurface (writer CITYGML_2)
GeometryValidator_3
    ISSUE_ATTR_NAME = _issues
    PRESETS = Custom
    REPAIR = YES
    RULES = CONSECUTIVE_IDENTICAL_VERTICES_2D CHECK_Z]YES]TOLERANCE]0.00173]FME_CONTROLLER_QUERY_FILE]]FME_CONTROLLER_CHOICE]CONSECUTIVE_IDENTICAL_VERTICES_2D SELF_INTERSECTING CHECK_HOLE_TOUCHING_POLYGON]No]CONNECT_Z_MODE_SI]FIRST_WINS]SELF_INTERSECTION_TOLERANCE]Automatic]VALIDATE_CURVES_POINTS]Yes]INTERSECT_ACROSS_MULTIS]No]FME_CONTROLLER_QUERY_FILE]]FME_CONTROLLER_CHOICE]SELF_INTERSECTING SHELL_VALIDATION FLIP_APPEARANCE_MODE]FLIP_APPEARANCES]FME_CONTROLLER_QUERY_FILE]]FME_CONTROLLER_CHOICE]SHELL_VALIDATION PLANAR_SURFACE CHECK_AREA]DO_NOT_CHECK_AREA]TOLERANCE_MODE]CUSTOM]TOLERANCE]0.00141]ANGULAR_TOLERANCE_MODE]AUTO]ANGULAR_TOLERANCE]<Unused>]FME_CONTROLLER_QUERY_FILE]]FME_CONTROLLER_CHOICE]PLANAR_SURFACE SOLID_VOID_REPAIR FME_CONTROLLER_QUERY_FILE]]FME_CONTROLLER_CHOICE]SOLID_VOID_REPAIR SURFACE_ORIENTATION FME_CONTROLLER_QUERY_FILE]]FME_CONTROLLER_CHOICE]SURFACE_ORIENTATION SOLID_ORIENTATION FME_CONTROLLER_QUERY_FILE]]FME_CONTROLLER_CHOICE]SOLID_ORIENTATION AREA_ORIENTATION AREA_ORIENTATION]VALID]FME_CONTROLLER_QUERY_FILE]]FME_CONTROLLER_CHOICE]AREA_ORIENTATION TYPE_REPAIR CONNECT_Z_MODE]FIRST_WINS]ARC_ENDPOINT_TOLERANCE_MODE]Custom]ARC_ENDPOINT_TOLERANCE]0.00141]FME_CONTROLLER_QUERY_FILE]]FME_CONTROLLER_CHOICE]TYPE_REPAIR
    SUMMARY = DETAILED_SUMMARY
    PASSED -> GroundSurface (writer CITYGML_2)
    REPAIRED -> Deaggregator
Deaggregator
    ATTR_ACCUM_MODE = HANDLE_CONFLICT
    ATTR_CONFLICT_RES = INCOMING_IF_CONFLICT
    EXPLODE_INSTANCES = No
    GEOM_LABEL_FIELD = _geometry_label
    LIST_ATTR_MODE_LOOKUP = LEAN
    PART_NUMBER_FIELD = _part_number
    RECURSIVE = No
    SPLIT_COMPOSITES = No
    DEAGGREGATED -> GroundSurface (writer CITYGML_2)
GeometryValidator_5
    ISSUE_ATTR_NAME = _issues
    PRESETS = Custom
    REPAIR = YES
    RULES = CONSECUTIVE_IDENTICAL_VERTICES_2D CHECK_Z]YES]TOLERANCE]0.00173]FME_CONTROLLER_QUERY_FILE]]FME_CONTROLLER_CHOICE]CONSECUTIVE_IDENTICAL_VERTICES_2D SELF_INTERSECTING CHECK_HOLE_TOUCHING_POLYGON]No]CONNECT_Z_MODE_SI]FIRST_WINS]SELF_INTERSECTION_TOLERANCE]Automatic]VALIDATE_CURVES_POINTS]Yes]INTERSECT_ACROSS_MULTIS]No]FME_CONTROLLER_QUERY_FILE]]FME_CONTROLLER_CHOICE]SELF_INTERSECTING SHELL_VALIDATION FLIP_APPEARANCE_MODE]FLIP_APPEARANCES]FME_CONTROLLER_QUERY_FILE]]FME_CONTROLLER_CHOICE]SHELL_VALIDATION PLANAR_SURFACE CHECK_AREA]DO_NOT_CHECK_AREA]TOLERANCE_MODE]CUSTOM]TOLERANCE]0.00141]ANGULAR_TOLERANCE_MODE]AUTO]ANGULAR_TOLERANCE]<Unused>]FME_CONTROLLER_QUERY_FILE]]FME_CONTROLLER_CHOICE]PLANAR_SURFACE SOLID_VOID_REPAIR FME_CONTROLLER_QUERY_FILE]]FME_CONTROLLER_CHOICE]SOLID_VOID_REPAIR SURFACE_ORIENTATION FME_CONTROLLER_QUERY_FILE]]FME_CONTROLLER_CHOICE]SURFACE_ORIENTATION SOLID_ORIENTATION FME_CONTROLLER_QUERY_FILE]]FME_CONTROLLER_CHOICE]SOLID_ORIENTATION AREA_ORIENTATION AREA_ORIENTATION]VALID]FME_CONTROLLER_QUERY_FILE]]FME_CONTROLLER_CHOICE]AREA_ORIENTATION TYPE_REPAIR CONNECT_Z_MODE]FIRST_WINS]ARC_ENDPOINT_TOLERANCE_MODE]Custom]ARC_ENDPOINT_TOLERANCE]0.00141]FME_CONTROLLER_QUERY_FILE]]FME_CONTROLLER_CHOICE]TYPE_REPAIR
    SUMMARY = DETAILED_SUMMARY
    PASSED -> BuildingPart (writer CITYGML_2)
    FAILED -> BuildingPart (writer CITYGML_2)
    REPAIRED -> BuildingPart (writer CITYGML_2)
GeometryValidator_6
    ISSUE_ATTR_NAME = _issues
    PRESETS = Custom
    REPAIR = YES
    RULES = CONSECUTIVE_IDENTICAL_VERTICES_2D CHECK_Z]YES]TOLERANCE]0.00173]FME_CONTROLLER_QUERY_FILE]]FME_CONTROLLER_CHOICE]CONSECUTIVE_IDENTICAL_VERTICES_2D SELF_INTERSECTING CHECK_HOLE_TOUCHING_POLYGON]No]CONNECT_Z_MODE_SI]FIRST_WINS]SELF_INTERSECTION_TOLERANCE]Automatic]VALIDATE_CURVES_POINTS]Yes]INTERSECT_ACROSS_MULTIS]No]FME_CONTROLLER_QUERY_FILE]]FME_CONTROLLER_CHOICE]SELF_INTERSECTING SHELL_VALIDATION FLIP_APPEARANCE_MODE]FLIP_APPEARANCES]FME_CONTROLLER_QUERY_FILE]]FME_CONTROLLER_CHOICE]SHELL_VALIDATION PLANAR_SURFACE CHECK_AREA]DO_NOT_CHECK_AREA]TOLERANCE_MODE]CUSTOM]TOLERANCE]0.00141]ANGULAR_TOLERANCE_MODE]AUTO]ANGULAR_TOLERANCE]<Unused>]FME_CONTROLLER_QUERY_FILE]]FME_CONTROLLER_CHOICE]PLANAR_SURFACE SOLID_VOID_REPAIR FME_CONTROLLER_QUERY_FILE]]FME_CONTROLLER_CHOICE]SOLID_VOID_REPAIR SURFACE_ORIENTATION FME_CONTROLLER_QUERY_FILE]]FME_CONTROLLER_CHOICE]SURFACE_ORIENTATION SOLID_ORIENTATION FME_CONTROLLER_QUERY_FILE]]FME_CONTROLLER_CHOICE]SOLID_ORIENTATION AREA_ORIENTATION AREA_ORIENTATION]VALID]FME_CONTROLLER_QUERY_FILE]]FME_CONTROLLER_CHOICE]AREA_ORIENTATION TYPE_REPAIR CONNECT_Z_MODE]FIRST_WINS]ARC_ENDPOINT_TOLERANCE_MODE]Custom]ARC_ENDPOINT_TOLERANCE]0.00141]FME_CONTROLLER_QUERY_FILE]]FME_CONTROLLER_CHOICE]TYPE_REPAIR
    SUMMARY = DETAILED_SUMMARY
    PASSED -> Building (writer CITYGML_2)
    FAILED -> Building (writer CITYGML_2)
    REPAIRED -> Building (writer CITYGML_2)

Bookmark: Reader Feature Types
WallSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_level_of_detail{} xml_buffer, BldgFaceID xml_buffer, DachName_LOD2 xml_buffer, DachTyp_LOD2 xml_buffer, DoorCount xml_buffer, FACEAREA xml_buffer, Innenwand xml_buffer, NORMAL_AZI xml_buffer, NORMAL_H xml_buffer, STRUKTUR xml_buffer, WindowPreference xml_buffer, Z_Differenz xml_buffer, Z_Fenster xml_buffer, Z_MAX_ASL xml_buffer, Z_MIN_ASL xml_buffer, Z_Max xml_buffer, Z_Min xml_buffer
    -> GeometryValidator_4
RoofSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_level_of_detail{} xml_buffer, BldgFaceID xml_buffer, DachName_LOD2 xml_buffer, DachTyp_LOD2 xml_buffer, FACEAREA xml_buffer, NORMAL_AZI xml_buffer, NORMAL_H xml_buffer, STRUKTUR xml_buffer, Z_MAX_ASL xml_buffer, Z_MIN_ASL xml_buffer, Z_Max xml_buffer, Z_Min xml_buffer
    -> GeometryValidator_2
GroundSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_level_of_detail{} xml_buffer, BldgFaceID xml_buffer, FACEAREA xml_buffer, STRUKTUR xml_buffer, Z_MIN_ASL xml_buffer, Z_Min xml_buffer
    -> GeometryValidator_3
BuildingPart (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_function xml_buffer, citygml_roof_type xml_buffer, citygml_measured_height xml_real64, citygml_measured_height_units xml_buffer, citygml_storeys_above_ground xml_uint64, citygml_storeys_below_ground xml_uint64, citygml_level_of_detail{} xml_buffer, citygml_outer_building_installation{}.xlink_href xml_buffer, citygml_bounded_by{}.xlink_href xml_buffer, citygml_consists_of_building_part{}.xlink_href xml_buffer, citygml_address{}.xlink_href xml_buffer, BldgPartID xml_buffer, DatenquelleBodenhoehe xml_buffer, DatenquelleDachhoehe xml_buffer, DatenquelleGeschossanzahl xml_buffer, DatenquelleLage xml_buffer, Grundrissaktualitaet xml_buffer
    -> GeometryValidator_5
Building (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_function xml_buffer, citygml_roof_type xml_buffer, citygml_measured_height xml_real64, citygml_measured_height_units xml_buffer, citygml_storeys_above_ground xml_uint64, citygml_storeys_below_ground xml_uint64, citygml_level_of_detail{} xml_buffer, citygml_outer_building_installation{}.xlink_href xml_buffer, citygml_bounded_by{}.xlink_href xml_buffer, citygml_consists_of_building_part{}.xlink_href xml_buffer, citygml_address{}.xlink_href xml_buffer, DatenquelleBodenhoehe xml_buffer, DatenquelleDachhoehe xml_buffer, DatenquelleGeschossanzahl xml_buffer, DatenquelleLage xml_buffer, Gemeindeschluessel xml_buffer, Geometrietyp2DReferenz xml_buffer, Grundrissaktualitaet xml_buffer,
      H_DGM xml_buffer, MaxHBuilding xml_buffer, MaxZBuilding xml_buffer, OBJEKT_ID xml_buffer, confidence xml_buffer, sst xml_buffer
    -> GeometryValidator_6
Address (reader CITYGML_1)
    attributes: citygml_target_uri xml_buffer, citygml_feature_role xml_buffer, citygml_feature_role_attr_name xml_buffer, citygml_feature_role_attr_val xml_buffer, gml_description xml_buffer, gml_name xml_buffer, citygml_address xml_xml
    -> Address (writer CITYGML_2)
CityModel (reader CITYGML_1)
    attributes: citygml_target_uri xml_buffer, gml_description xml_buffer, gml_name xml_buffer, citygml_city_object_member{}.xlink_href xml_buffer, citygml_appearance_member{}.xlink_href xml_buffer, gml_feature_member{}.xlink_href xml_buffer
    -> CityModel (writer CITYGML_2)

Bookmark: Writer Feature Types
WallSurface (writer CITYGML_2)
    attributes: gml_id xml_buffer, gml_parent_id xml_buffer, citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_level_of_detail{} xml_buffer, BldgFaceID xml_buffer, DachName_LOD2 xml_buffer, DachTyp_LOD2 xml_buffer, DoorCount xml_buffer, FACEAREA xml_buffer, Innenwand xml_buffer, NORMAL_AZI xml_buffer, NORMAL_H xml_buffer, STRUKTUR xml_buffer, WindowPreference xml_buffer, Z_Differenz xml_buffer, Z_Fenster xml_buffer, Z_MAX_ASL xml_buffer, Z_MIN_ASL xml_buffer, Z_Max xml_buffer,
      Z_Min xml_buffer, _issues{}.count xml_uint32, _issues{}.issue_found xml_buffer, _issues{}.location_sample.x xml_real64, _issues{}.location_sample.y xml_real64, _issues{}.location_sample.z xml_real64
RoofSurface (writer CITYGML_2)
    attributes: gml_id xml_buffer, gml_parent_id xml_buffer, citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_level_of_detail{} xml_buffer, BldgFaceID xml_buffer, DachName_LOD2 xml_buffer, DachTyp_LOD2 xml_buffer, FACEAREA xml_buffer, NORMAL_AZI xml_buffer, NORMAL_H xml_buffer, STRUKTUR xml_buffer, Z_MAX_ASL xml_buffer, Z_MIN_ASL xml_buffer, Z_Max xml_buffer, Z_Min xml_buffer, _issues{}.count xml_uint32, _issues{}.issue_found xml_buffer, _issues{}.location_sample.x xml_real64, _issues{}.location_sample.y xml_real64,
      _issues{}.location_sample.z xml_real64
GroundSurface (writer CITYGML_2)
    attributes: gml_id xml_buffer, gml_parent_id xml_buffer, citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_level_of_detail{} xml_buffer, BldgFaceID xml_buffer, FACEAREA xml_buffer, STRUKTUR xml_buffer, Z_MIN_ASL xml_buffer, Z_Min xml_buffer, _issues{}.count xml_uint32, _issues{}.issue_found xml_buffer, _issues{}.location_sample.x xml_real64, _issues{}.location_sample.y xml_real64, _issues{}.location_sample.z xml_real64, _part_number xml_uint64, _geometry_label xml_buffer
BuildingPart (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_function xml_buffer, citygml_roof_type xml_buffer, citygml_measured_height xml_real64, citygml_measured_height_units xml_buffer, citygml_storeys_above_ground xml_uint64, citygml_storeys_below_ground xml_uint64, citygml_level_of_detail{} xml_buffer, citygml_outer_building_installation{}.xlink_href xml_buffer, citygml_bounded_by{}.xlink_href xml_buffer, citygml_consists_of_building_part{}.xlink_href xml_buffer, citygml_address{}.xlink_href xml_buffer, BldgPartID xml_buffer, DatenquelleBodenhoehe xml_buffer, DatenquelleDachhoehe xml_buffer, DatenquelleGeschossanzahl xml_buffer, DatenquelleLage xml_buffer, Grundrissaktualitaet xml_buffer, _issues{}.count xml_uint32,
      _issues{}.issue_found xml_buffer, _issues{}.location_sample.x xml_real64, _issues{}.location_sample.y xml_real64, _issues{}.location_sample.z xml_real64, _issues{}.repair_state xml_buffer
Building (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_function xml_buffer, citygml_roof_type xml_buffer, citygml_measured_height xml_real64, citygml_measured_height_units xml_buffer, citygml_storeys_above_ground xml_uint64, citygml_storeys_below_ground xml_uint64, citygml_level_of_detail{} xml_buffer, citygml_outer_building_installation{}.xlink_href xml_buffer, citygml_bounded_by{}.xlink_href xml_buffer, citygml_consists_of_building_part{}.xlink_href xml_buffer, citygml_address{}.xlink_href xml_buffer, DatenquelleBodenhoehe xml_buffer, DatenquelleDachhoehe xml_buffer, DatenquelleGeschossanzahl xml_buffer, DatenquelleLage xml_buffer, Gemeindeschluessel xml_buffer, Geometrietyp2DReferenz xml_buffer, Grundrissaktualitaet xml_buffer,
      H_DGM xml_buffer, MaxHBuilding xml_buffer, MaxZBuilding xml_buffer, OBJEKT_ID xml_buffer, confidence xml_buffer, sst xml_buffer, _issues{}.count xml_uint32, _issues{}.issue_found xml_buffer, _issues{}.location_sample.x xml_real64, _issues{}.location_sample.y xml_real64, _issues{}.location_sample.z xml_real64, _issues{}.repair_state xml_buffer
Address (writer CITYGML_2)
    attributes: citygml_target_uri xml_buffer, citygml_feature_role xml_buffer, citygml_feature_role_attr_name xml_buffer, citygml_feature_role_attr_val xml_buffer, gml_description xml_buffer, gml_name xml_buffer, citygml_address xml_xml
CityModel (writer CITYGML_2)
    attributes: citygml_target_uri xml_buffer, gml_description xml_buffer, gml_name xml_buffer, citygml_city_object_member{}.xlink_href xml_buffer, citygml_appearance_member{}.xlink_href xml_buffer, gml_feature_member{}.xlink_href xml_buffer
